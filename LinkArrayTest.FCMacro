# Check https://github.com/FreeCAD/FreeCAD/blob/master/src/Mod/TemplatePyMod/TaskPanel.py

from os.path import expanduser
from PySide import QtGui, QtCore
import Draft

# Better way of looking for the ui
param = FreeCAD.ParamGet("User parameter:BaseApp/Preferences/Macro")
macroPath = param.GetString("MacroPath", "") + "/"
uiLocation = path.replace("\\", "/")
uiLocation = uiLocation + "LinkArrayTest.ui"



def onDelete(key):
    if key == QtCore.Qt.Key_Delete:
        print("delete")


class SelectionObserver:
    def __init__(self, selList=None):
        self.baseSelection = None
        self.selList = selList  # list to store selections

    def addSelection(self, doc, obj, sub, pos):
        test = Gui.Selection.getSelectionEx("", 0)[0]
        # the first element is the name of the object we want to use
        # Note that if an object inside a sub-assembly is selected, this method will get the entire sub-assembly
        splitedName = test.SubElementNames[0].split(".")
        if self.selList and not self.selList.findItems(splitedName[0], QtCore.Qt.MatchExactly):
            if self.selList.count() < 1:
                self.selList.addItem(splitedName[0])
            else:
                self.selList.takeItem(0)
                self.selList.addItem(splitedName[0])


class CustomEventFilter(QtCore.QObject):
    def eventFilter(self, obj, event):
        # We will look if focus to the qlistwidget is lost in order to deselect items
        if event.type() == QtCore.QEvent.FocusOut:
            selectedItems = obj.selectedItems()
            for item in selectedItems:
                item.setSelected(False)
            return True
        elif event.type() == QtCore.QEvent.FocusIn:
            Gui.Selection.clearSelection()      # we don't need the selected objects anymore
            return True
        else:
            return QtCore.QObject.eventFilter(self, obj, event)


class LinkArrayTestTaskPanel:
    def __init__(self):
        self.form = Gui.PySideUic.loadUi(uiLocation)
        self.baseSelect = False  # used to know if we are looking for bases
        self.centerSelect = False   # The same than for baseSelect
        self.obs = None
        # Setup of objects
        self.form.baseList.setContextMenuPolicy(QtCore.Qt.ActionsContextMenu)
        self.form.centerList.setContextMenuPolicy(QtCore.Qt.ActionsContextMenu)
        self.form.centerList.installEventFilter(CustomEventFilter(self.form.centerList))
        self.form.baseList.installEventFilter(CustomEventFilter(self.form.baseList))
        self.setActions()           # Adding actions to objects
        # connect signals and slots
        self.form.baseSelect.clicked.connect(self.baseSelectClick)
        self.form.centerSelect.clicked.connect(self.centerSelectClick)

    def setActions(self):
        baseListDelete = QtGui.QAction("Delete", self.form.baseList)
        centerListDelete = QtGui.QAction("Delete", self.form.baseList)
        centerListDelete.setShortcut(QtGui.QKeySequence.Delete)
        baseListDelete.setShortcut(QtGui.QKeySequence.Delete)
        baseListDelete.setShortcutContext(QtCore.Qt.WidgetWithChildrenShortcut)
        centerListDelete.setShortcutContext(QtCore.Qt.WidgetWithChildrenShortcut)
        self.form.baseList.addAction(baseListDelete)
        self.form.centerList.addAction(centerListDelete)
        QtCore.QObject.connect(baseListDelete, QtCore.SIGNAL("triggered()"), self.deleteSelectedItems)
        QtCore.QObject.connect(centerListDelete, QtCore.SIGNAL("triggered()"), self.deleteSelectedItems)

    def baseSelectClick(self):
        if not self.baseSelect:
            self.clearSelections()
            self.form.baseSelect.setText("Selecting")
            self.obs = SelectionObserver(self.form.baseList)
            Gui.Selection.addObserver(self.obs)
        else:
            self.form.baseSelect.setText("Select")
            self.obs.selList = None     # stop selecting more items
            Gui.Selection.removeObserver(self.obs)
        self.baseSelect = not self.baseSelect   # Toggle every time the button is pressed

    def centerSelectClick(self):
        if not self.centerSelect:
            self.clearSelections()
            self.form.centerSelect.setText("Selecting")
            self.obs = SelectionObserver(self.form.centerList)
            Gui.Selection.addObserver(self.obs)
        else:
            self.form.centerSelect.setText("Select")
            self.obs.setList = None     # stop selecting more items
            Gui.Selection.removeObserver(self.obs)
        self.centerSelect = not self.centerSelect

    def accept(self):
        self.clearSelections()
        Gui.Control.closeDialog()
        if self.form.baseList.count() > 0:
            self.createArray()
        if self.obs is not None:
            Gui.Selection.removeObserver(self.obs)  # make sure that the selection observer is deleted

    def reject(self):
        Gui.Control.closeDialog()
        if self.obs is not None:
            Gui.Selection.removeObserver(self.obs)  # make sure that the selection observer is deleted

    def deleteSelectedItems(self):
        baseSelItems = self.form.baseList.selectedItems()
        centerSelItems = self.form.centerList.selectedItems()
        if baseSelItems:
            for item in baseSelItems:
                self.form.baseList.takeItem(self.form.baseList.row(item))
        if centerSelItems:
            for item in centerSelItems:
                self.form.centerList.takeItem(self.form.baseList.row(item))

    def clearSelections(self):
        # make sure to not have both selection buttons on
        if self.baseSelect:
            self.baseSelectClick()
        if self.centerSelect:
            self.centerSelectClick()

    def createArray(self):
        base = App.ActiveDocument.getObject(self.form.baseList.item(0).text())
        name = self.form.nameEdit.text()

        # Assuming we are making arrays of links
        if self.form.arrayType.currentText() == "Polar":
            center = App.ActiveDocument.getObject(self.form.centerList.item(0).text())
            baseCenter = base.Placement.Base
            centerCenter = center.Placement.Base
            ArrayCenter = centerCenter - baseCenter
            Draft.makeArray(base, ArrayCenter, 360, 5,  name=name, useLink=True)
        else:
            Draft.makeArray(base, App.Vector(10, 0, 0),
                            App.Vector(0, 1, 0), 2, 1, useLink=True, name=name)
        App.ActiveDocument.recompute()

panel = LinkArrayTestTaskPanel()
Gui.Control.showDialog(panel)
